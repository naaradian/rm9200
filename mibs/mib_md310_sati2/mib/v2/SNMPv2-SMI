SNMPv2-SMI DEFINITIONS ::= BEGIN


-- the path to the root

org OBJECT IDENTIFIER 	::= { 1  3 }

--  "iso" = 1

dod OBJECT IDENTIFIER 	::= { org 6 }

internet OBJECT IDENTIFIER 	::= { dod 1 }

directory OBJECT IDENTIFIER 	::= { internet 1 }

mgmt OBJECT IDENTIFIER 	::= { internet 2 }

mib-2 OBJECT IDENTIFIER 	::= { mgmt 1 }

transmission OBJECT IDENTIFIER 	::= { mib-2 10 }

experimental OBJECT IDENTIFIER 	::= { internet 3 }

private OBJECT IDENTIFIER 	::= { internet 4 }

enterprises OBJECT IDENTIFIER 	::= { private 1 }

security OBJECT IDENTIFIER 	::= { internet 5 }

snmpV2 OBJECT IDENTIFIER 	::= { internet 6 }

-- transport domains

snmpDomains OBJECT IDENTIFIER 	::= { snmpV2 1 }

-- transport proxies

snmpProxys OBJECT IDENTIFIER 	::= { snmpV2 2 }

-- module identities

snmpModules OBJECT IDENTIFIER 	::= { snmpV2 3 }

-- Extended UTCTime, to allow dates with four-digit years
-- (Note that this definition of ExtUTCTime is not to be IMPORTed
--  by MIB modules.)

ExtUTCTime ::= OCTET STRING (SIZE (11 | 13))


-- format is YYMMDDHHMMZ or YYYYMMDDHHMMZ
--   where: YY   - last two digits of year (only years
--                 between 1900-1999)
--          YYYY - last four digits of the year (any year)
--          MM   - month (01 through 12)
--          DD   - day of month (01 through 31)
--          HH   - hours (00 through 23)
--          MM   - minutes (00 through 59)
--          Z    - denotes GMT (the ASCII character Z)
--
-- For example, "9502192015Z" and "199502192015Z" represent
-- 8:15pm GMT on 19 February 1995. Years after 1999 must use
-- the four digit year format. Years 1900-1999 may use the
-- two or four digit format.
-- MACRO definitions removed because they are not SMI
--
-- definitions of administrative identifiers

zeroDotZero OBJECT-IDENTITY
	STATUS current
	DESCRIPTION
		"A value used for null identifiers."
	::= { 0  0 }

END
